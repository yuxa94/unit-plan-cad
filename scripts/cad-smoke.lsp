;;; Scratch drawing only. Load cad-guard.lsp first, then this file through MCP.
;;; (up:smoke "C:/job/smoke.dwg" "C:/job/operations" "C:/my-local-project/profile/parts/my-part.dwg")
;;; Creates five model objects in an EMPTY scratch drawing. Fixed geometry is a
;;; setup test, not a drafting template. Existing receipts prevent replay.
(vl-load-com)
(defun up:json-string (s / i c out)
  (setq i 1 out "")
  (repeat (strlen s)
    (setq c (substr s i 1) i (1+ i))
    (setq out (strcat out (cond ((= c "\\") "\\\\") ((= c "\"") "\\\"") ((= c (chr 10)) "\\n") ((= c (chr 13)) "\\r") (T c)))))
  (strcat "\"" out "\""))
(defun up:smoke (expected job part /)
  (up:run expected job "installation-smoke"
    '(lambda (doc / ms pts boundary loop hatch dim label block style font stream countBefore)
      (setq ms (vla-get-ModelSpace doc) countBefore (vla-get-Count ms))
      (if (/= countBefore 0) (error "Smoke test requires an empty scratch drawing"))
      (if (not (findfile part)) (error "Native DWG part missing"))
      (setq font (findfile (strcat (getenv "WINDIR") "/Fonts/malgun.ttf")))
      (if (not font) (error "Korean smoke font malgun.ttf missing from Windows Fonts; choose an installed Korean font before testing"))
      (setq style (vl-catch-all-apply 'vla-Item (list (vla-get-TextStyles doc) "UP-SMOKE")))
      (if (vl-catch-all-error-p style) (setq style (vla-Add (vla-get-TextStyles doc) "UP-SMOKE")))
      (vla-put-FontFile style font)
      (setq pts (vlax-make-safearray vlax-vbDouble '(0 . 7)))
      (vlax-safearray-fill pts '(0.0 0.0 1000.0 0.0 1000.0 500.0 0.0 500.0))
      (setq boundary (vla-AddLightWeightPolyline ms pts))
      (vla-put-Closed boundary :vlax-true)
      (setq hatch (vla-AddHatch ms 1 "ANSI31" :vlax-true))
      (setq loop (vlax-make-safearray vlax-vbObject '(0 . 0)))
      (vlax-safearray-put-element loop 0 boundary)
      (vla-AppendOuterLoop hatch loop)
      (vla-put-PatternScale hatch 20.0)
      (vla-Evaluate hatch)
      (setq dim (vla-AddDimRotated ms (vlax-3d-point 0 0 0) (vlax-3d-point 1000 0 0) (vlax-3d-point 500 -300 0) 0.0))
      (vla-put-TextHeight dim 60.0)
      (vla-put-ArrowheadSize dim 40.0)
      (setq label (vla-AddText ms "단위세대 MCP 설치시험" (vlax-3d-point 0 800 0) 100.0))
      (vla-put-StyleName label "UP-SMOKE")
      (setq block (vla-InsertBlock ms (vlax-3d-point 2000 0 0) (findfile part) 1.0 1.0 1.0 0.0))
      (vla-Regen doc 1)
      (vla-Save doc)
      (setq stream (open (strcat job "/smoke-readback.json") "w" "utf8"))
      (write-line (strcat "{\"document\":" (up:json-string (vla-get-FullName doc))
        ",\"model_count\":" (itoa (vla-get-Count ms))
        ",\"korean_text\":" (up:json-string (vla-get-TextString label))
        ",\"dimension_measurement\":" (rtos (vla-get-Measurement dim) 2 6)
        ",\"hatch_area\":" (rtos (vla-get-Area hatch) 2 6)
        ",\"hatch_pattern\":" (up:json-string (vla-get-PatternName hatch))
        ",\"block_name\":" (up:json-string (vla-get-Name block)) "}") stream)
      (close stream))))
(princ)
